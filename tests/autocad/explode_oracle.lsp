(defun ae:emit (value)
  (write-line value ae:out)
  (princ (strcat "\nAE|" value))
)

(defun ae:point (x y z) (list x y z))

(defun ae:line ()
  (entmakex '((0 . "LINE") (10 0.0 0.0 0.0) (11 10.0 0.0 0.0)))
)

(defun ae:circle ()
  (entmakex '((0 . "CIRCLE") (10 0.0 0.0 0.0) (40 . 2.0)))
)

(defun ae:poly ()
  (entmakex '((0 . "LWPOLYLINE") (100 . "AcDbEntity")
    (100 . "AcDbPolyline") (90 . 4) (70 . 1)
    (10 0.0 0.0) (10 10.0 0.0) (10 10.0 10.0) (10 0.0 10.0)))
)

(defun ae:hatch (pattern)
  (entmakex (append
    '((0 . "HATCH") (100 . "AcDbEntity") (100 . "AcDbHatch")
      (10 0.0 0.0 0.0) (210 0.0 0.0 1.0))
    (list (cons 2 pattern) (cons 70 (if (= pattern "SOLID") 1 0)))
    '((71 . 0) (91 . 1) (92 . 2) (72 . 0) (73 . 1) (93 . 4)
      (10 0.0 0.0) (10 10.0 0.0) (10 10.0 10.0) (10 0.0 10.0)
      (97 . 0) (75 . 0) (76 . 1))
    (if (= pattern "SOLID")
      '((98 . 0))
      '((52 . 0.0) (41 . 1.0) (77 . 0) (78 . 1) (53 . 45.0)
        (43 . 0.0) (44 . 0.0) (45 . -2.1213203435596424)
        (46 . 2.1213203435596424) (79 . 0) (98 . 0))))
  )
)

(defun ae:block (name flags /)
  (entmake (list '(0 . "BLOCK") (cons 2 name) (cons 70 flags) '(10 0.0 0.0 0.0)))
  (entmake '((0 . "CIRCLE") (10 0.0 0.0 0.0) (40 . 2.0)))
  (entmake '((0 . "LINE") (10 0.0 0.0 0.0) (11 10.0 0.0 0.0)))
  (entmake '((0 . "ENDBLK")))
)

(defun ae:polyface (indices / point)
  (entmake '((0 . "POLYLINE") (66 . 1) (10 0.0 0.0 0.0) (70 . 64) (71 . 4) (72 . 1)))
  (foreach point '((0.0 0.0 0.0) (10.0 0.0 0.0) (10.0 10.0 0.0) (0.0 10.0 0.0))
    (entmake (list '(0 . "VERTEX") '(70 . 192) (cons 10 point))))
  (entmake (append '((0 . "VERTEX") (70 . 128) (10 0.0 0.0 0.0))
    (mapcar 'cons '(71 72 73 74) indices)))
  (entmake '((0 . "SEQEND")))
)

(defun ae:polygonmesh (closed / i j)
  (entmake (list '(0 . "POLYLINE") '(66 . 1) '(10 0.0 0.0 0.0)
    (cons 70 (+ 16 closed)) '(71 . 3) '(72 . 3)))
  (setq i 0)
  (repeat 3
    (setq j 0)
    (repeat 3
      (entmake (list '(0 . "VERTEX") '(70 . 64) (cons 10 (list (* 10.0 i) (* 10.0 j) 0.0))))
      (setq j (1+ j)))
    (setq i (1+ i)))
  (entmake '((0 . "SEQEND")))
)

(defun ae:run (label creator / marker source item data status count)
  (entmakex '((0 . "POINT") (10 9999.0 9999.0 9999.0)))
  (setq marker (entlast))
  (setq status (vl-catch-all-apply creator '()))
  (if (vl-catch-all-error-p status)
    (ae:emit (strcat label "|CREATE_ERROR|" (vl-catch-all-error-message status)))
    (progn
      (setq source (entlast))
      (if (or (null source) (= source marker))
        (ae:emit (strcat label "|CREATE_FAILED"))
        (progn
          (ae:emit (strcat label "|SOURCE|" (vl-prin1-to-string (entget source))))
          (ae:emit (strcat label "|SOURCE_TYPE|" (cdr (assoc 0 (entget source)))))
          (setq status (vl-catch-all-apply '(lambda () (command-s "_.explode" source "")) '()))
          (if (vl-catch-all-error-p status)
            (ae:emit (strcat label "|EXPLODE_ERROR|" (vl-catch-all-error-message status))))
          (ae:emit (strcat label "|SOURCE_SURVIVES|" (if (entget source) "YES" "NO")))
          (setq item (entnext marker) count 0)
          (while item
            (setq data (entget item))
            (if (and data (not (equal item source)))
              (progn
                (setq count (1+ count))
                (ae:emit (strcat label "|RESULT_TYPE|" (cdr (assoc 0 data))))
                (ae:emit (strcat label "|RESULT|" (vl-prin1-to-string data)))))
            (setq item (entnext item)))
          (ae:emit (strcat label "|RESULT_COUNT|" (itoa count)))
        )
      )
    )
  )
  (princ)
)

(defun ae:main (/ saved variable)
  (setq ae:root (getenv "ACADRUST_ORACLE_ROOT"))
  (setq ae:out (open (strcat ae:root "/target/explode-oracle/runtime.txt") "w"))
  (setq saved (mapcar '(lambda (variable) (cons variable (getvar variable)))
    '("CMDECHO" "OSMODE" "FILEDIA" "EXPERT")))
  (setvar "CMDECHO" 0)
  (setvar "OSMODE" 0)
  (setvar "FILEDIA" 0)
  (setvar "EXPERT" 5)
  (command "_.-dimstyle" "_restore" "Standard")
  (setvar "DIMSCALE" 1.0)
  (setvar "DIMTXT" 2.5)
  (setvar "DIMASZ" 2.5)
  (setvar "DIMEXO" 0.625)
  (setvar "DIMEXE" 1.25)
  (setvar "DIMBLK" "")
  (setvar "DIMBLK1" "")
  (setvar "DIMBLK2" "")
  (setvar "DIMSAH" 0)
  (setvar "DIMTXSTY" "Standard")
  (setvar "CMLSCALE" 2.0)
  (ae:emit (strcat "VERSION|" (getvar "ACADVER") "|" (getvar "PRODUCT")))
  (ae:run "POINT" '(lambda () (entmakex '((0 . "POINT") (10 0.0 0.0 0.0)))))
  (ae:run "LINE" 'ae:line)
  (ae:run "CIRCLE" 'ae:circle)
  (ae:run "ARC" '(lambda () (entmakex '((0 . "ARC") (10 0.0 0.0 0.0) (40 . 2.0) (50 . 0.0) (51 . 1.5707963267948966)))))
  (ae:run "ELLIPSE" '(lambda () (entmakex '((0 . "ELLIPSE") (100 . "AcDbEntity") (100 . "AcDbEllipse") (10 0.0 0.0 0.0) (11 4.0 0.0 0.0) (40 . 0.5) (41 . 0.0) (42 . 6.283185307179586) (210 0.0 0.0 1.0)))))
  (ae:run "SPLINE" '(lambda () (entmakex '((0 . "SPLINE") (100 . "AcDbEntity") (100 . "AcDbSpline") (70 . 0) (71 . 3) (72 . 8) (73 . 4) (74 . 0) (40 . 0.0) (40 . 0.0) (40 . 0.0) (40 . 0.0) (40 . 1.0) (40 . 1.0) (40 . 1.0) (40 . 1.0) (10 0.0 0.0 0.0) (10 0.0 5.0 0.0) (10 10.0 5.0 0.0) (10 10.0 0.0 0.0)))))
  (ae:run "HELIX" '(lambda () (command "_.helix" "_non" '(0.0 0.0 0.0) 2.0 2.0 5.0)))
  (ae:run "SOLID" '(lambda () (entmakex '((0 . "SOLID") (10 0.0 0.0 0.0) (11 10.0 0.0 0.0) (12 0.0 10.0 0.0) (13 10.0 10.0 0.0)))))
  (ae:run "3DFACE" '(lambda () (entmakex '((0 . "3DFACE") (10 0.0 0.0 0.0) (11 10.0 0.0 0.0) (12 10.0 10.0 0.0) (13 0.0 10.0 0.0)))))
  (ae:run "TEXT" '(lambda () (entmakex '((0 . "TEXT") (10 0.0 0.0 0.0) (40 . 2.5) (1 . "Example")))))
  (ae:run "RAY" '(lambda () (entmakex '((0 . "RAY") (100 . "AcDbEntity") (100 . "AcDbRay") (10 0.0 0.0 0.0) (11 1.0 0.0 0.0)))))
  (ae:run "XLINE" '(lambda () (entmakex '((0 . "XLINE") (100 . "AcDbEntity") (100 . "AcDbXline") (10 0.0 0.0 0.0) (11 1.0 0.0 0.0)))))
  (ae:run "LWPOLYLINE" 'ae:poly)
  (ae:run "POLYLINE2D" '(lambda ()
    (entmake '((0 . "POLYLINE") (66 . 1) (10 0.0 0.0 0.0) (70 . 0)))
    (entmake '((0 . "VERTEX") (10 0.0 0.0 0.0) (42 . 1.0)))
    (entmake '((0 . "VERTEX") (10 10.0 0.0 0.0)))
    (entmake '((0 . "VERTEX") (10 10.0 10.0 0.0)))
    (entmake '((0 . "SEQEND")))))
  (ae:run "POLYLINE3D" '(lambda () (command "_.3dpoly" "_non" '(0.0 0.0 0.0) "_non" '(10.0 0.0 10.0) "_non" '(10.0 10.0 0.0) "")))
  (ae:run "POLYFACE_POINT" '(lambda () (ae:polyface '(1 0 0 0))))
  (ae:run "POLYFACE_LINE" '(lambda () (ae:polyface '(1 2 0 0))))
  (ae:run "POLYFACE_TRIANGLE" '(lambda () (ae:polyface '(1 2 3 0))))
  (ae:run "POLYFACE_QUAD" '(lambda () (ae:polyface '(1 2 3 4))))
  (ae:run "POLYGONMESH_OPEN" '(lambda () (ae:polygonmesh 0)))
  (ae:run "POLYGONMESH_CLOSED_M" '(lambda () (ae:polygonmesh 1)))
  (ae:run "POLYGONMESH_CLOSED_N" '(lambda () (ae:polygonmesh 32)))
  (ae:run "POLYGONMESH_CLOSED_MN" '(lambda () (ae:polygonmesh 33)))
  (ae:run "MTEXT" '(lambda () (entmakex '((0 . "MTEXT") (100 . "AcDbEntity") (100 . "AcDbMText") (10 0.0 0.0 0.0) (40 . 2.5) (41 . 30.0) (71 . 1) (1 . "First\\PSecond")))))
  (ae:run "MTEXT_FORMATTED" '(lambda () (entmakex '((0 . "MTEXT") (100 . "AcDbEntity") (100 . "AcDbMText") (10 0.0 0.0 0.0) (40 . 2.5) (41 . 100.0) (71 . 1) (1 . "A{\\C1;RED}B{\\H2x;BIG}")))))
  (ae:run "HATCH_PATTERN" '(lambda () (ae:hatch "ANSI31")))
  (ae:run "HATCH_SOLID" '(lambda () (ae:hatch "SOLID")))
  (ae:run "MLINE" '(lambda () (command "_.mline" "_non" '(0.0 0.0 0.0) "_non" '(10.0 0.0 0.0) "")))
  (ae:run "LEADER_STRAIGHT" '(lambda () (entmakex '((0 . "LEADER") (100 . "AcDbEntity") (100 . "AcDbLeader") (3 . "Standard") (71 . 1) (72 . 0) (73 . 3) (74 . 0) (75 . 0) (40 . 2.5) (41 . 5.0) (76 . 3) (10 0.0 0.0 0.0) (10 10.0 10.0 0.0) (10 15.0 10.0 0.0) (210 0.0 0.0 1.0)))))
  (ae:run "LEADER_SPLINE" '(lambda () (entmakex '((0 . "LEADER") (100 . "AcDbEntity") (100 . "AcDbLeader") (3 . "Standard") (71 . 1) (72 . 1) (73 . 3) (74 . 0) (75 . 0) (40 . 2.5) (41 . 5.0) (76 . 3) (10 0.0 0.0 0.0) (10 10.0 10.0 0.0) (10 15.0 10.0 0.0) (210 0.0 0.0 1.0)))))
  (ae:run "DIM_LINEAR" '(lambda () (command "_.dimlinear" "_non" '(0.0 0.0 0.0) "_non" '(10.0 0.0 0.0) "_non" '(0.0 5.0 0.0))))
  (ae:run "DIM_ALIGNED" '(lambda () (command "_.dimaligned" "_non" '(0.0 0.0 0.0) "_non" '(10.0 5.0 0.0) "_non" '(0.0 10.0 0.0))))
  (ae:run "REGION" '(lambda () (ae:poly) (command "_.region" (entlast) "")))
  (ae:run "PLANESURFACE" '(lambda () (command "_.planesurf" "_non" '(0.0 0.0 0.0) "_non" '(10.0 10.0 0.0))))
  (ae:run "3DSOLID_BOX" '(lambda () (command "_.box" "_non" '(0.0 0.0 0.0) "_non" '(10.0 10.0 0.0) 10.0)))
  (ae:block "AE_BLOCK" 0)
  (ae:run "INSERT_UNIFORM" '(lambda () (entmakex '((0 . "INSERT") (2 . "AE_BLOCK") (10 0.0 0.0 0.0) (41 . 1.0) (42 . 1.0) (43 . 1.0)))))
  (ae:run "INSERT_NONUNIFORM" '(lambda () (entmakex '((0 . "INSERT") (2 . "AE_BLOCK") (10 0.0 0.0 0.0) (41 . 2.0) (42 . 1.0) (43 . 1.0)))))
  (ae:run "MINSERT" '(lambda () (entmakex '((0 . "INSERT") (2 . "AE_BLOCK") (10 0.0 0.0 0.0) (41 . 1.0) (42 . 1.0) (43 . 1.0) (70 . 2) (71 . 2) (44 . 20.0) (45 . 20.0)))))
  (entmake '((0 . "BLOCK") (2 . "AE_ATTRIBUTES") (70 . 0) (10 0.0 0.0 0.0)))
  (entmake '((0 . "ATTDEF") (10 1.0 1.0 0.0) (40 . 2.5) (1 . "Default value") (3 . "Prompt") (2 . "TAG") (70 . 0)))
  (entmake '((0 . "LINE") (10 0.0 0.0 0.0) (11 10.0 0.0 0.0)))
  (entmake '((0 . "ENDBLK")))
  (ae:run "INSERT_ATTRIBUTES" '(lambda ()
    (entmake '((0 . "INSERT") (2 . "AE_ATTRIBUTES") (66 . 1) (10 20.0 20.0 0.0)))
    (entmake '((0 . "ATTRIB") (10 21.0 21.0 0.0) (40 . 2.5) (1 . "Instance value") (2 . "TAG") (70 . 0)))
    (entmake '((0 . "SEQEND")))))
  (command "_.-wblock" (strcat ae:root "/target/explode-oracle/ae_xref.dwg") "AE_BLOCK")
  (ae:run "XREF" '(lambda () (command "_.-xref" "_attach" (strcat ae:root "/target/explode-oracle/ae_xref.dwg") "_non" '(0.0 0.0 0.0) 1.0 1.0 0.0)))
  (ae:run "AEC_WALL" '(lambda ()
    (command "_.walladd" "_non" '(0.0 0.0 0.0) "_non" '(10.0 0.0 0.0) "")))
  (ae:emit "DONE")
  (foreach variable saved (setvar (car variable) (cdr variable)))
  (close ae:out)
  (setq ae:out nil)
  (princ "\nAE|DONE\n")
  (princ)
)

(ae:main)
(princ)
