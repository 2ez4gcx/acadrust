(vl-load-com)

(defun r12c:emit (key value)
  (write-line (strcat key "\t" (vl-prin1-to-string value)) r12c:report))

(defun r12c:array (type values / array)
  (setq array (vlax-make-safearray type (cons 0 (1- (length values)))))
  (vlax-safearray-fill array values)
  (vlax-make-variant array))

(defun r12c:polyline (points flags / point)
  (entmake (list '(0 . "POLYLINE") '(8 . "GEOMETRY") '(66 . 1) '(10 0.0 0.0 0.0) (cons 70 flags)))
  (foreach point points
    (entmake (list '(0 . "VERTEX") '(8 . "GEOMETRY") (cons 10 point) (cons 70 (if (= (logand flags 8) 8) 32 0)))))
  (entmake '((0 . "SEQEND") (8 . "GEOMETRY"))))

(defun r12c:mesh (/ point)
  (entmake '((0 . "POLYLINE") (8 . "GEOMETRY") (66 . 1) (10 0.0 0.0 0.0) (70 . 16) (71 . 2) (72 . 3)))
  (foreach point '((30.0 0.0 0.0) (30.0 5.0 1.0) (30.0 10.0 2.0) (40.0 0.0 3.0) (40.0 5.0 4.0) (40.0 10.0 5.0))
    (entmake (list '(0 . "VERTEX") '(8 . "GEOMETRY") (cons 10 point) '(70 . 64))))
  (entmake '((0 . "SEQEND") (8 . "GEOMETRY"))))

(defun r12c:geometry (doc / block model face insert attributes attribute)
  (setq model (vla-get-ModelSpace doc))
  (setq block (vla-Add (vla-get-Blocks doc) (vlax-3d-point '(2.0 3.0 0.0)) "NATIVE_PART"))
  (vla-AddLine block (vlax-3d-point '(0.0 0.0 0.0)) (vlax-3d-point '(5.0 0.0 0.0)))
  (vla-AddPolyline block (r12c:array vlax-vbDouble '(0.0 0.0 0.0 5.0 5.0 0.0 10.0 0.0 0.0)))
  (vla-AddAttribute block 2.5 0 "Native attribute" (vlax-3d-point '(1.0 1.0 0.0)) "TAG" "default")
  (setq insert (vla-InsertBlock model (vlax-3d-point '(10.0 20.0 0.0)) "NATIVE_PART" 1.0 1.0 1.0 0.0))
  (setq attributes (vlax-safearray->list (vlax-variant-value (vla-GetAttributes insert))))
  (vla-put-TextString (car attributes) "native-value")
  (r12c:polyline '((0.0 0.0 0.0) (5.0 2.0 0.0) (10.0 0.0 0.0)) 1)
  (r12c:polyline '((0.0 15.0 0.0) (5.0 17.0 3.0) (10.0 15.0 7.0)) 8)
  (r12c:mesh)
  (vla-AddPolyfaceMesh model
    (r12c:array vlax-vbDouble '(50.0 0.0 0.0 60.0 0.0 0.0 60.0 10.0 3.0 50.0 10.0 0.0))
    (r12c:array vlax-vbInteger '(1 2 3 4)))
  (vla-AddText model "NATIVE R12" (vlax-3d-point '(0.0 30.0 0.0)) 2.5)
  (command "_.ZOOM" "_Extents")
  (setq r12c:insert insert r12c:block block))

(defun r12c:viewport (doc / paper viewport layer)
  (setq layer (vla-Add (vla-get-Layers doc) "FROZEN_PROBE"))
  (vla-AddLine (vla-get-ModelSpace doc) (vlax-3d-point '(0.0 0.0 0.0)) (vlax-3d-point '(100.0 50.0 0.0)))
  (setq line (vla-AddCircle (vla-get-ModelSpace doc) (vlax-3d-point '(40.0 30.0 0.0)) 12.0))
  (vla-put-Layer line "FROZEN_PROBE")
  (setvar "TILEMODE" 0)
  (vla-put-MSpace doc :vlax-false)
  (vla-put-ActiveSpace doc 0)
  (command "_.PSPACE")
  (setq paper (vla-get-PaperSpace doc))
  (vlax-for entity paper
    (if (/= (vla-get-ObjectName entity) "AcDbViewport") (vla-Delete entity)))
  (foreach center '((70.0 45.0 0.0) (210.0 45.0 0.0))
    (command "_.MVIEW" (list (- (car center) 60.0) (- (cadr center) 40.0)) (list (+ (car center) 60.0) (+ (cadr center) 40.0)))
    (setq viewport (vlax-ename->vla-object (entlast)))
    (vla-Display viewport :vlax-true)
    (vla-put-Target viewport (vlax-3d-point '(4.0 5.0 6.0)))
    (vla-put-Direction viewport (vlax-3d-point '(1.0 2.0 3.0)))
    (vla-put-TwistAngle viewport (/ pi 6.0))
    (vla-put-LensLength viewport 65.0)
    (vla-put-SnapBasePoint viewport (vlax-3d-point '(2.0 3.0 0.0)))
    (vla-SetSnapSpacing viewport 0.25 0.75)
    (vla-SetGridSpacing viewport 5.0 10.0)
    (vla-put-SnapOn viewport :vlax-true)
    (vla-put-GridOn viewport :vlax-true)
    (vla-put-SnapRotationAngle viewport (/ pi 9.0)))
  (vla-AddLine paper (vlax-3d-point '(0.0 0.0 0.0)) (vlax-3d-point '(280.0 90.0 0.0)))
  (setq r12c:viewport viewport)
  (command "_.ZOOM" "_Extents"))

(defun r12c:header (doc / ucs view)
  (vla-AddLine (vla-get-ModelSpace doc) (vlax-3d-point '(0.0 0.0 0.0)) (vlax-3d-point '(100.0 60.0 0.0)))
  (setvar "SNAPBASE" '(2.0 3.0))
  (setvar "SNAPUNIT" '(0.25 0.75))
  (setvar "SNAPANG" (/ pi 9.0))
  (setvar "SNAPMODE" 1)
  (setvar "GRIDUNIT" '(5.0 10.0))
  (setvar "GRIDMODE" 1)
  (setvar "UCSICON" 3)
  (setvar "UNITMODE" 1)
  (command "_.VIEWRES" "_Yes" 1200)
  (setvar "ORTHOMODE" 1)
  (setq ucs (vla-Add (vla-get-UserCoordinateSystems doc)
    (vlax-3d-point '(4.0 5.0 6.0)) (vlax-3d-point '(4.0 6.0 6.0))
    (vlax-3d-point '(3.0 5.0 6.0)) "NATIVE_UCS"))
  (vla-put-ActiveUCS doc ucs)
  (if (not (tblsearch "UCS" "NATIVE_UCS")) (error "Native UCS setup failed"))
  (command "_.PLAN" "_Current")
  (command "_.ZOOM" "_Center" '(10.0 20.0) 80.0)
  (setq view (vla-Add (vla-get-Views doc) "NATIVE_VIEW"))
  (vla-put-Height view 80.0)
  (vla-put-Width view 120.0)
  (vla-put-Target view (vlax-3d-point '(4.0 5.0 6.0)))
  (vla-put-Direction view (vlax-3d-point '(0.0 0.0 1.0)))
  (if (not (tblsearch "VIEW" "NATIVE_VIEW")) (error "Native VIEW setup failed"))
  (r12c:emit "setup.ucs" (tblsearch "UCS" "NATIVE_UCS"))
  (r12c:emit "setup.unit-mode" (getvar "UNITMODE")))

(defun r12c:save (doc path type / result)
  (setq result (vl-catch-all-apply 'vla-SaveAs (list doc path type)))
  (if (vl-catch-all-error-p result)
    (progn (r12c:emit "ERROR" (vl-catch-all-error-message result)) (exit)))
  (r12c:emit "saved" (list path type)))

(defun r12c:create (directory kind / *error* doc variables base)
  (defun *error* (message)
    (if r12c:report (progn (r12c:emit "ERROR" message) (close r12c:report) (setq r12c:report nil)))
    (princ))
  (setq r12c:report (open (strcat directory "/" kind ".generation.txt") "w"))
  (setq variables (mapcar '(lambda (name) (cons name (getvar name))) '("FILEDIA" "CMDECHO" "EXPERT" "AUDITCTL")))
  (setvar "FILEDIA" 0) (setvar "CMDECHO" 1) (setvar "EXPERT" 5)
  (setq doc (vla-get-ActiveDocument (vlax-get-acad-object)))
  (vlax-for entity (vla-get-ModelSpace doc) (vla-Delete entity))
  (vla-Add (vla-get-Layers doc) "GEOMETRY")
  (cond ((= kind "native-geometry") (r12c:geometry doc))
        ((= kind "native-viewports") (r12c:viewport doc))
        ((= kind "native-header") (r12c:header doc)))
  (setq base (strcat directory "/" kind))
  (r12c:save doc (strcat base "-modern.dwg") 64)
  (r12c:save doc (strcat base ".dwg") -3)
  (r12c:save doc (strcat base ".dxf") 1)
  (cond
    ((= kind "native-geometry")
      (vla-put-TextString (car (vlax-safearray->list (vlax-variant-value (vla-GetAttributes r12c:insert)))) "edited-value")
      (vla-AddLine r12c:block (vlax-3d-point '(0.0 7.0 0.0)) (vlax-3d-point '(8.0 7.0 0.0))))
    ((= kind "native-viewports") (vla-put-TwistAngle r12c:viewport (/ pi 4.0)))
    ((= kind "native-header") (setvar "SNAPUNIT" '(0.5 1.5)) (setvar "GRIDUNIT" '(6.0 12.0))))
  (r12c:save doc (strcat base "-edited.dwg") -3)
  (if (= kind "native-geometry")
    (progn
      (setvar "ISAVEPERCENT" 100)
      (repeat 3
        (vla-put-TextString (car (vlax-safearray->list (vlax-variant-value (vla-GetAttributes r12c:insert)))) "temporary-value")
        (vla-Save doc)
        (vla-put-TextString (car (vlax-safearray->list (vlax-variant-value (vla-GetAttributes r12c:insert)))) "edited-value")
        (vla-Save doc))
      (if (findfile (strcat base "-incremental.dwg")) (vl-file-delete (strcat base "-incremental.dwg")))
      (vl-file-copy (strcat base "-edited.dwg") (strcat base "-incremental.dwg"))
      (r12c:emit "incremental-save" T)))
  (r12c:save doc (strcat base "-edited.dxf") 1)
  (r12c:emit "COMPLETE" T)
  (close r12c:report) (setq r12c:report nil)
  (foreach variable variables (setvar (car variable) (cdr variable)))
  (command "_.QUIT" "_No")
  (princ))
