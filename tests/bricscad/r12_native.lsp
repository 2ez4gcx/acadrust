(defun ar12:emit (key value)
  (write-line (strcat key "\t" (vl-prin1-to-string value)) ar12:report))

(defun ar12:check (key actual expected)
  (ar12:emit key (list (if (equal actual expected 0.00000001) "PASS" "FAIL") actual expected)))

(defun ar12:selection-count (kind / selection)
  (setq selection (ssget "_X" (list (cons 0 kind))))
  (if selection (sslength selection) 0))

(defun ar12:polyline (entity / child data points kind elevation)
  (setq data (entget entity) kind (cdr (assoc 0 data)) points nil)
  (ar12:check "polyline.kind" (not (null (member kind '("POLYLINE" "LWPOLYLINE")))) T)
  (if (= kind "LWPOLYLINE")
    (progn
      (setq elevation (if (assoc 38 data) (cdr (assoc 38 data)) 0.0))
      (foreach item data
        (if (= (car item) 10) (setq points (append points (list (append (cdr item) (list elevation))))))))
    (progn
      (setq child (entnext entity))
      (while (and child (= (cdr (assoc 0 (setq data (entget child)))) "VERTEX"))
        (setq points (append points (list (cdr (assoc 10 data)))) child (entnext child)))
      (ar12:check "polyline.seqend" (cdr (assoc 0 (entget child))) "SEQEND")))
  (ar12:check "polyline.vertices" points '((1.0 2.0 0.0) (8.0 9.0 0.0))))

(defun ar12:validate (name / selection entity attribute data block mesh-count polyface-count poly3d-count)
  (cond
    ((wcmatch name "NATIVE-GEOMETRY*")
      (ar12:check "insert.count" (ar12:selection-count "INSERT") 1)
      (ar12:check "text.count" (ar12:selection-count "TEXT") 1)
      (setq selection (ssget "_X" '((0 . "POLYLINE"))))
      (setq mesh-count 0 polyface-count 0 poly3d-count 0)
      (if selection
        (repeat (sslength selection)
          (setq entity (ssname selection 0) data (entget entity))
          (cond ((= (logand (cdr (assoc 70 data)) 64) 64) (setq polyface-count (1+ polyface-count)))
                ((= (logand (cdr (assoc 70 data)) 16) 16) (setq mesh-count (1+ mesh-count)))
                ((= (logand (cdr (assoc 70 data)) 8) 8) (setq poly3d-count (1+ poly3d-count))))
          (ssdel entity selection)))
      (ar12:check "polygon-mesh.count" mesh-count 1)
      (ar12:check "polyface.count" polyface-count 1)
      (ar12:check "polyline3d.count" poly3d-count 1)
      (setq selection (ssget "_X" '((0 . "INSERT"))))
      (if selection
        (ar12:check "attribute.value" (cdr (assoc 1 (entget (entnext (ssname selection 0)))))
          (if (wcmatch name "*EDITED*,*INCREMENTAL*") "edited-value" "native-value"))))
    ((wcmatch name "NATIVE-VIEWPORTS*")
      (ar12:check "viewport.count" (ar12:selection-count "VIEWPORT") 4)
      (setq selection (ssget "_X" '((0 . "VIEWPORT"))))
      (if selection
        (repeat (sslength selection)
          (setq entity (ssname selection 0) data (entget entity))
          (if (equal (cdr (assoc 40 data)) 120.0 0.00000001)
            (progn
              (ar12:check "viewport.target" (cdr (assoc 17 data)) '(4.0 5.0 6.0))
              (ar12:check "viewport.direction" (cdr (assoc 16 data)) '(1.0 2.0 3.0))
              (ar12:check "viewport.twist" (cdr (assoc 51 data))
                (if (and (wcmatch name "*EDITED*") (= (car (cdr (assoc 10 data))) 210.0)) (/ pi 4.0) (/ pi 6.0)))
              (ar12:check "viewport.snap-angle" (cdr (assoc 50 data)) (/ pi 9.0))
              (ar12:check "viewport.snap-base" (cdr (assoc 13 data)) '(2.0 3.0 0.0))
              (ar12:check "viewport.snap-spacing" (cdr (assoc 14 data)) '(0.25 0.75 0.0))
              (ar12:check "viewport.grid-spacing" (cdr (assoc 15 data)) '(5.0 10.0 0.0))))
          (ssdel entity selection))))
    ((wcmatch name "NATIVE-HEADER*")
      (ar12:check "header.snap-mode" (getvar "SNAPMODE") 1)
      (ar12:check "header.grid-mode" (getvar "GRIDMODE") 1)
      (ar12:emit "header.unit-mode" (getvar "UNITMODE"))
      (ar12:check "header.snap-base" (getvar "SNAPBASE") '(2.0 3.0))
      (ar12:check "header.snap-spacing" (getvar "SNAPUNIT") (if (wcmatch name "*EDITED*") '(0.5 1.5) '(0.25 0.75)))
      (ar12:check "header.grid-spacing" (getvar "GRIDUNIT") (if (wcmatch name "*EDITED*") '(6.0 12.0) '(5.0 10.0)))
      (ar12:emit "header.ucs-name" (getvar "UCSNAME"))
      (ar12:emit "header.ucs-origin" (getvar "UCSORG"))
      (setq data (tblsearch "UCS" "NATIVE_UCS"))
      (ar12:check "header.named-ucs-origin" (cdr (assoc 10 data)) '(4.0 5.0 6.0))
      (ar12:check "header.named-ucs-x" (cdr (assoc 11 data)) '(0.0 1.0 0.0))
      (ar12:check "header.named-ucs-y" (cdr (assoc 12 data)) '(-1.0 0.0 0.0)))
    ((wcmatch name "MODEL-POLYLINE*")
      (ar12:check "point.count" (ar12:selection-count "POINT") 1)
      (ar12:check "polyline.count" (ar12:selection-count "POLYLINE,LWPOLYLINE") 1)
      (setq selection (ssget "_X" '((0 . "POLYLINE,LWPOLYLINE"))))
      (if selection (ar12:polyline (ssname selection 0))))
    ((wcmatch name "BLOCK-POLYLINE*")
      (ar12:check "point.count" (ar12:selection-count "POINT") 1)
      (ar12:check "model-polyline.count" (ar12:selection-count "POLYLINE,LWPOLYLINE") 0)
      (setq block (tblobjname "BLOCK" "PART"))
      (ar12:check "block.present" (not (null block)) T)
      (if block (ar12:polyline (entnext block))))
    ((wcmatch name "INSERT-ATTRIBUTES*")
      (ar12:check "point.count" (ar12:selection-count "POINT") 1)
      (ar12:check "insert.count" (ar12:selection-count "INSERT") 1)
      (setq selection (ssget "_X" '((0 . "INSERT"))))
      (if selection
        (progn
          (setq entity (ssname selection 0) attribute (entnext entity) data (entget attribute))
          (ar12:check "insert.block" (cdr (assoc 2 (entget entity))) "PART")
          (ar12:check "attribute.kind" (cdr (assoc 0 data)) "ATTRIB")
          (ar12:check "attribute.value" (cdr (assoc 1 data)) "value")
          (ar12:check "attribute.tag" (cdr (assoc 2 data)) "TAG")
          (ar12:check "attribute.owner" (cdr (assoc 330 data)) entity)
          (ar12:check "insert.seqend" (cdr (assoc 0 (entget (entnext attribute)))) "SEQEND"))))
    ((wcmatch name "SHAPE-MENU*")
      (ar12:check "shape.count" (ar12:selection-count "SHAPE") 1)
      (setq selection (ssget "_X" '((0 . "SHAPE"))))
      (if selection
        (progn
          (setq data (entget (ssname selection 0)))
          (ar12:emit "shape.data" data)
          (ar12:check "shape.name" (cdr (assoc 2 data)) "BOX")
          (ar12:check "shape.size" (cdr (assoc 40 data)) 2.0))))
    (T (ar12:emit "ERROR" "Unknown fixture"))))

(defun ar12:run (report-path expected-name / *error* variables)
  (defun *error* (message)
    (if ar12:report
      (progn (ar12:emit "ERROR" message) (close ar12:report) (setq ar12:report nil)))
    (princ))
  (setq ar12:report (open report-path "w"))
  (ar12:check "opened-file" (strcase (getvar "DWGNAME")) (strcase expected-name))
  (ar12:emit "cad.version" (getvar "ACADVER"))
  (setq variables (mapcar '(lambda (name) (cons name (getvar name))) '("CMDECHO" "FILEDIA" "EXPERT" "AUDITCTL")))
  (setvar "CMDECHO" 1)
  (setvar "FILEDIA" 0)
  (setvar "EXPERT" 5)
  (setvar "AUDITCTL" 1)
  (command "_.AUDIT" "_No")
  (ar12:emit "audit.completed" T)
  (ar12:validate (strcase expected-name))
  (ar12:emit "COMPLETE" T)
  (close ar12:report)
  (setq ar12:report nil)
  (foreach variable variables (setvar (car variable) (cdr variable)))
  (command "_.QUIT" "_Yes")
  (princ))
