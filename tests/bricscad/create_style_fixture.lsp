(vl-load-com)
(defun ar:create-style-fixture (base / doc dict style styleobj output)
  (setq doc (vla-get-ActiveDocument (vlax-get-acad-object)))
  (setq dict (dictsearch (namedobjdict) "ACAD_TABLESTYLE"))
  (setq style (dictsearch (cdr (assoc -1 dict)) "Standard"))
  (setq styleobj (vlax-ename->vla-object (cdr (assoc -1 style))))
  (setq output (open (strcat base ".before.txt") "w"))
  (write-line (vl-prin1-to-string (entget (cdr (assoc -1 style)))) output)
  (close output)
  (vla-put-TitleSuppressed styleobj :vlax-true)
  (vla-put-HeaderSuppressed styleobj :vlax-true)
  (setq output (open (strcat base ".txt") "w"))
  (write-line (vl-prin1-to-string (entget (cdr (assoc -1 style)))) output)
  (close output)
  (vla-SaveAs doc (strcat base ".dwg") 48)
  (vla-SaveAs doc (strcat base ".dxf") 49)
  (command "_.QUIT" "_No")
  (princ))
